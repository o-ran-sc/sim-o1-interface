module o-ran-ald {
  yang-version 1.1;
  namespace "urn:o-ran:ald:1.0";
  prefix "o-ran-ald";

  import o-ran-ald-port {
    prefix "ap";
  }

  organization "O-RAN Alliance";

  contact
    "www.o-ran.org";

  description
    "This module defines the module for the ALD communication.

    Copyright 2019 the O-RAN Alliance.

    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.

    Redistribution and use in source and binary forms, with or without
    modification, are permitted provided that the following conditions are met:

    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision "2021-12-01" {
    description
      "version 1.2.0

      1) Typographical corrections.";

    reference "ORAN-WG4.M.0-v01.00";
  }

  revision "2019-07-03" {
    description
      "version 1.1.0

      1) backward compatible changes to introduce groupings.";

    reference "ORAN-WG4.M.0-v01.00";
  }

  revision "2019-02-04" {
    description
      "version 1.0.0

      1) imported model from xRAN
      2) changed namespace and reference from xran to o-ran";

    reference "ORAN-WG4.M.0-v01.00";
  }

  grouping ald-input {
    description "a grouping for ald input";
    leaf port-id {
      type leafref {
        path "/ap:ald-ports-io/ap:ald-port/ap:port-id";
      }
      mandatory true;
      description
        "Unique ALD port identifier reported by radio";
    }

    leaf ald-req-msg {
      type binary {
        length "0..1200";
      }

      description
        "Response message to be forwarded to ALD in type of binary-string";
    }
  }

  grouping ald-output {
    description "a grouping for ald output";
    leaf port-id {
      type leafref {
        path "/ap:ald-ports-io/ap:ald-port/ap:port-id";
      }
      mandatory true;
      description
        "Unique ALD port identifier reported by radio";
    }

    leaf status {
      type enumeration {
        enum ACCEPTED {
          description
            "Operation was accepted, message was processed towards ALD and response is provided";
        }
        enum REJECTED {
          description
            "Operation was rejected by O-RU";
        }
      }
      mandatory true;

      description
        "Status of RPC handling seen from equipment perspective";
    }

    leaf error-message {
      when "../status='REJECTED'";
      type string;

      description
        "Detailed error message when the status is rejected. E.g. wrong ALD port identifier was used in RPC received from NETCONF Client";
    }

    leaf ald-resp-msg {
      type binary {
        length "0..1200";
      }

      description
        "Response message forwarded from ALD in type of binary-string";
    }

    leaf frames-with-wrong-crc {
      type uint32;

      description
        "Number of frames with incorrect CRC (FCS) received from ALD - running counter";
    }

    leaf frames-without-stop-flag {
      type uint32;

      description
        "Number of frames without stop flag received from ALD - running counter";
    }

    leaf number-of-received-octets {
      type uint32;

      description
        "Number of octets received from HDLC bus - running counter";
    }
  }
  // rpc-statements
  rpc ald-communication {
    description
      "RPC to support communication between O-DU and Antenna Line Devices";

    input {
      uses ald-input;
    }

    output {
      uses ald-output;
    }
  }
}
