module o-ran-troubleshooting {
  yang-version 1.1;
  namespace "urn:o-ran:troubleshooting:1.0";
  prefix "o-ran-trblsht";

  organization "O-RAN Alliance";

  contact
    "www.o-ran.org";

  description
    "This module defines the operations for the troubleshooting logs.

    Copyright 2019 the O-RAN Alliance.

    THIS SOFTWARE IS PROVIDED BY THE COPYRIGHT HOLDERS AND CONTRIBUTORS 'AS IS'
    AND ANY EXPRESS OR IMPLIED WARRANTIES, INCLUDING, BUT NOT LIMITED TO, THE
    IMPLIED WARRANTIES OF MERCHANTABILITY AND FITNESS FOR A PARTICULAR PURPOSE
    ARE DISCLAIMED. IN NO EVENT SHALL THE COPYRIGHT HOLDER OR CONTRIBUTORS BE
    LIABLE FOR ANY DIRECT, INDIRECT, INCIDENTAL, SPECIAL, EXEMPLARY, OR
    CONSEQUENTIAL DAMAGES (INCLUDING, BUT NOT LIMITED TO, PROCUREMENT OF
    SUBSTITUTE GOODS OR SERVICES; LOSS OF USE, DATA, OR PROFITS; OR BUSINESS
    INTERRUPTION) HOWEVER CAUSED AND ON ANY THEORY OF LIABILITY, WHETHER IN
    CONTRACT, STRICT LIABILITY, OR TORT (INCLUDING NEGLIGENCE OR OTHERWISE)
    ARISING IN ANY WAY OUT OF THE USE OF THIS SOFTWARE, EVEN IF ADVISED OF THE
    POSSIBILITY OF SUCH DAMAGE.

    Redistribution and use in source and binary forms, with or without
    modification, are permitted provided that the following conditions are met:

    * Redistributions of source code must retain the above copyright notice,
    this list of conditions and the above disclaimer.
    * Redistributions in binary form must reproduce the above copyright notice,
    this list of conditions and the above disclaimer in the documentation
    and/or other materials provided with the distribution.
    * Neither the Members of the O-RAN Alliance nor the names of its
    contributors may be used to endorse or promote products derived from
    this software without specific prior written permission.";

  revision "2022-08-15" {
    description
      "version 1.2.0

      1) clarified path/folder description.";

    reference "ORAN-WG4.M.0-v01.00";
  }

  revision "2021-12-01" {
    description
      "version 1.1.0

      1) typographical corrections";

    reference "ORAN-WG4.M.0-v01.00";
  }

  revision "2019-02-04" {
    description
      "version 1.0.0

      1) imported model from xRAN
      2) changed namespace and reference from xran to o-ran";

    reference "ORAN-WG4.M.0-v01.00";
  }


  grouping troubleshooting-status-grouping {
    description "grouping used for troubleshooting RPCs";
    leaf status {
      type enumeration {
        enum SUCCESS {
          description "RPC completed correctly";
        }
        enum FAILURE {
          description "RPC failed";
        }
      }
      description "result of RPC operation";
    }
    leaf failure-reason {
      when "../status = 'FAILURE'";
      type string;
      description "free-form text description why error occurred";
    }
  }

  rpc start-troubleshooting-logs {
    description
      "Management plane triggered to start collecting the troubleshooting logs files of O-RU.";
      output {
        uses troubleshooting-status-grouping;
      }
  }

  rpc stop-troubleshooting-logs {
    description
      "Management plane triggered to stop collecting the troubleshooting logs files of O-RU.";
      output {
        uses troubleshooting-status-grouping;
      }
  }

  notification troubleshooting-log-generated {
    description
      "When new log file generated, send this notification.";
    leaf-list log-file-name {
      type string;
      description
        "The list of troubleshooting log file names on the O-RU. Each record in this list is expected to
        contain location of the file (e.g. 'o-ran/log/') and the name of file (e.g.'my_troubleshooting_log_file.zip',
        where 'my_troubleshooting_log_file' is example file name and 'zip' is expected file name extension).
        Example complete expected content of this node is 'o-ran/log/my_troubleshooting_log_file.zip'.";
    }
  }
}
