module onap-system {
  yang-version 1.1;
  namespace "urn:onap:system";
  prefix os;

  import ietf-inet-types {
    prefix inet;
  }
  import ietf-system {
    prefix sys;
  }

  organization
    "ONAP - Open Network Automation Platform";
  contact
    "Web: <https://www.onap.org>
     Editors:
        Alex Stancu <mailto:alexandru.stancu@highstreet-technologies.com>
        Adrian Lita <mailto:adrian.lita@highstreet-technologies.com>
        Martin Skorupski <mailto:martin.skorupski@highstreet-technologies.com>";
  description
    "This module augments ietf-system with ONAP details.

     Copyright 2020 the O-RAN Alliance.

     Licensed under the Apache License, Version 2.0 (the 'License');
     you may not use this file except in compliance with the License.
     You may obtain a copy of the License at

     http://www.apache.org/licenses/LICENSE-2.0

     Unless required by applicable law or agreed to in writing, software
     distributed under the License is distributed on an 'AS IS' BASIS,
     WITHOUT WARRANTIES OR CONDITIONS OF ANY KIND, either express or implied.
     See the License for the specific language governing permissions and
     limitations under the License.";

  revision 2022-11-04 {
    description
      "Geographical location added to 'system'.";
    reference
      "Project specific";
  }

  revision 2020-10-26 {
    description
      "Initial revision for the ietf-system augmentation for ONAP.";
    reference
      "https://jira.onap.org/browse/SDNC-1396";
  }

  typedef geographic-coordinate-degree {
    type decimal64 {
      fraction-digits 8;
    }
    description
      "Decimal degree (DD) used to express latitude and longitude
       geographic coordinates.";
  }

  augment "/sys:system" {
    description
      "Enhancing the system information.";
    leaf name {
      type string;
      description
        "The name of the system.";
    }
    leaf web-ui {
      type inet:uri;
      description
        "The URI of the system Web UI.";
    }
    container geographical-location {
      description
        "Containes information about geo location";
      leaf altitude {
        type int64;
        units "millimeter";
        description
          "Distance above the sea level.";
      }
      leaf latitude {
        type geographic-coordinate-degree {
          range "-90..90";
        }
        description
          "Relative position north or south on the Earth's surface.";
      }
      leaf longitude {
        type geographic-coordinate-degree {
          range "-180..180";
        }
        description
          "Angular distance east or west on the Earth's surface.";
      }
    }
  }
}
